Ativo DEFINITIONS AUTOMATIC TAGS ::=
BEGIN

Publish ::= SEQUENCE {
	subject OBJECT IDENTIFIER,
	value BOOLEAN
}

Subscribe ::= SEQUENCE {
	subject OBJECT IDENTIFIER
}

Unsubscribe ::= SEQUENCE {
	subject OBJECT IDENTIFIER
}

Notify ::= SEQUENCE {
	subject OBJECT IDENTIFIER,
	value BOOLEAN,
	ip PrintableString(SIZE(1..256))
}

ACKsubs ::= SEQUENCE {
	subject OBJECT IDENTIFIER,
	value BOOLEAN
}

Ativo ::= SEQUENCE {
  id CHOICE {
  	pub Publish,
	sub Subscribe,
	un Unsubscribe,
	noty Notify,
	ack ACKsubs 
  },
  cod INTEGER
}

END
